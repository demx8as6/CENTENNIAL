module optional-vs-mandatory {
    namespace "uri:optional:vs:mandatory";
    prefix ovm;
    
    organization
      "ONF (Open Networking Foundation) Open Transport Working Group - Wireless Transport Project";
      
    contact
      "WG Web:   <https://www.opennetworking.org/technical-communities/areas/specification/1931-optical-transport>
       WG List:  <mailto:wireless-transport@login.opennetworking.org >
       WG Chair: Lyndon Ong 
                 <mailto:lyong@ciena.com>
       WG Chair: Giorgio Cazzaniga <>
                 <mailto:giorgio.cazzaniga@sm-optics.com>
       Editor:   Martin Skorupski
                 <mailto:martin.skorupski@highstreet-technologies.com>";
    description
      "This module contains a collection of YANG definitions for
       managing microwave transport networks.";
       
    revision 2016-06-30 {
      description
        "Initial revision.";
      reference
        "ONF TR xyz: A YANG Data Model for Microwave Transport Networks.";
    }
    
    /*
     * Features
     */
    feature leaf-x12 {
      description
        "This feature indicates that the device allows the configuration of leafs with names ending with '12'.";
    }
  
    feature leaf-x13 {
      description
        "This feature indicates that the device allows the configuration of leafs with names ending with '13'.";
    }
  
    container testContainer {
      leaf leaf111 {
        type boolean;
        default true;
      }
      leaf leaf112 {
      if-feature leaf-x12;
        type string;
        default "my-default";
      }
      leaf leaf113 {
      if-feature leaf-x13;
        type int32;
        default -99;
      }
      leaf leaf114 {
        type uint32;
        default 100;
      }
    } 
  
    list testList {
      key uuid;
      leaf uuid {
        mandatory true;
        type string;
      }
      leaf leaf211 {
        type boolean;
        default true;
      }
      leaf leaf212 {
      if-feature leaf-x12;
        type string;
        default "my-default";
      }
      leaf leaf213 {
      if-feature leaf-x13;
        type int32;
        default -99;
      }
      leaf leaf214 {
        type uint32;
        default 100;
      }
    } 
  }
