module CoreModelForMicrowave-CoreFoundationModule-SuperClassesAndCommonPackages {
    namespace "uri:onf:CoreModelForMicrowave-CoreFoundationModule-SuperClassesAndCommonPackages";
    prefix CoreModelForMicrowave-CoreFoundationModule-SuperClassesAndCommonPackages;

    import CoreModelForMicrowave-CoreFoundationModule-StateModel {
        prefix CoreModelForMicrowave-CoreFoundationModule-StateModel;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-05 {
        description 
            "Initial revision."; 
        reference 
            "ONF TR xyz: A YANG Data Model for Microwave Transport Networks."; 
    }

    grouping Name {
        description "Name: A property of an entity with a value that is unique in some namespace but may change during the life of the entity. A name carries no semantics with respect to the purpose of the entity.";
        list nameList {
            description "List of names.";
            config true;
            ordered-by system;
            uses NameAndValue;
            min-elements 1;
        }
    }
    grouping GlobalClass {
        description "Represents a type of thing (an Entity) that has instances which can exist in their own right (independently of any others).



Entity: Has identity, defined boundary, properties, functionality and lifecycle in a global context.



(consider in the context of an Object Class: (usage) The representation of a thing that may be an entity or an inseparable Entity Feature)";
        uses Name;
        uses Label;
        uses Extension;
        uses CoreModelForMicrowave-CoreFoundationModule-StateModel:State_Pac;
        list localIdList {
            description "An identifier that is unique in the context of some scope that is less than the global scope.



(consider in the context of Identifier: A property of an entity/role with a value that is unique within an identifier space, where the identifier space is itself unique, and immutable. The identifier therefore represents the identity of the entity/role. An identifier carries no semantics with respect to the purpose of the entity.)";
            config true;
            ordered-by system;
            uses NameAndValue;
        }
        leaf uuid {
            type UniversalId;
            description "UUID: An identifier that is universally unique



(consider in the context of Identifier: A property of an entity/role with a value that is unique within an identifier space, where the identifier space is itself globally unique, and immutable. An identifier carries no semantics with respect to the purpose or state of the entity)";
        }
    }
    grouping LocalClass {
        description "A LocalClass represents a Feature of an Entity. It is inseparable from a GlobalClass but is a distinct feature of that GlobalClass such that the instances of LocalClass are able to have associations to other instances..

Feature of an Entity: An inseparable, externally distinguishable part of an entity.

The mandatory LocalId of the LocalClass instance is unique in the context of the GlobalClass from which it is inseparable.

(consider in the context of an Object Class: (usage) The representation of a thing that may be an entity or an inseparable feature of an entity)

";
        uses Name;
        uses Label;
        uses Extension;
        uses CoreModelForMicrowave-CoreFoundationModule-StateModel:State_Pac;
        list localIdList {
            description "An identifier that is unique in the context of some scope that is less than the global scope.



(consider in the context of Identifier: A property of an entity/role with a value that is unique within an identifier space, where the identifier space is itself unique, and immutable. The identifier therefore represents the identity of the entity/role. An identifier carries no semantics with respect to the purpose of the entity.)";
            config true;
            ordered-by system;
            uses NameAndValue;
            min-elements 1;
        }
    }
    grouping Label {
        description "A property of an entity with a value that is not expected to be unique and is allowed to change. A label carries no semantics with respect to the purpose of the entity and has no effect on the entity behavior or state.";
        list labelList {
            description "List of labels.";
            config true;
            ordered-by system;
            uses NameAndValue;
        }
    }
    grouping Extension {
        description "Extension provides an opportunity to define properties not declared in the class that extend the class enabling a realization with simple ad-hoc extension of standard classes to be conformant.";
        list extensionList {
            description "List of simple name-value extentions";
            config true;
            ordered-by system;
            uses NameAndValue;
        }
    }
    grouping UniversalIdAuthority {
        description "Represents the authority that controls the allocation of UUIDs.
            lifecycle:Preliminary";
        leaf uuid {
            type UniversalId;
            description "The UUID for the UUID authority.";
        }
    }
    grouping NameAndValueAuthority {
        description "Represents the authority that controls the legal valuse for the names and values of a name/value attribute.
            lifecycle:Preliminary";
        leaf uuid {
            type UniversalId;
            description "The UUID for the NameValueAuthority.";
        }
    }
    grouping ConditionalPackage {
        description "The base class for conditional packages.
            lifecycle:Experimental";
        uses Extension;
        uses Label;
    }
    grouping NameAndValue {
        description "A scoped name-value pair";
        leaf valueName {
            type string;
            description "The name of the value. The value need not have a name.";
        }
        leaf value {
            type string;
            description "The value";
        }
        leaf _nameAndValueAuthorityRef {
            type leafref {
                path '/NameAndValueAuthority/';
            }
            description "The authority that defines the named value.";
        }
        leaf _globalClassRef {
            type leafref {
                path '/GlobalClass/';
            }
            description "The scope of the name uniqueness";
        }
        leaf _localClassRef {
            type leafref {
                path '/LocalClass/';
            }
            description "The scope of the name uniqueness";
        }
    }
    typedef UniversalId {
        description "The univeral ID value where the mechanism for generation is defned by some authority not directly referenced in the structure.";
        type string;
    }
}
