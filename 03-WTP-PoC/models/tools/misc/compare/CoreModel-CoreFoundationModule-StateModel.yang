module CoreModel-CoreFoundationModule-StateModel {
    namespace "uri:onf:CoreModel-CoreFoundationModule-StateModel";
    prefix CoreModel-CoreFoundationModule-StateModel;


    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-05 {
        description 
            "Initial revision."; 
        reference 
            "ONF TR xyz: A YANG Data Model for Microwave Transport Networks."; 
    }

    grouping State_Pac {
        description "Provides general state attributes.
            lifecycle:Preliminary";
        leaf operationalState {
            type OperationalState;
            config false;
            description "The operational state is used to indicate whether or not the resource is installed and working";
        }
        leaf administrativeControl {
            type AdministrativeControl;
            description "The administrativeControl state provides control of the availability of specific resources without modification to the provisioning of those resources.
                The value is the current control target. The actual administrativeState may or may not be at target.";
        }
        leaf adminsatratveState {
            type AdministrativeState;
            config false;
            description "Shows whether or not the client has permission to use or has a prohibition against using the resource.
                The administrative state expresses usage permissions for specific resources without modification to the provisioning of those resources.";
        }
        leaf lifecycleState {
            type LifecycleState;
            description "Used to track the planned deployment, allocation to clients and withdrawal of resources. ";
        }
    }
    typedef OperationalState {
        description "The possible values of the operationalState.
            lifecycle:Preliminary";
        type enumeration {
            enum DISABLED;
            enum ENABLED;
        }
    }
    typedef AdministrativeState {
        description "The possible values of the administrativeState.
            lifecycle:Preliminary";
        type enumeration {
            enum LOCKED;
            enum UNLOCKED;
        }
    }
    typedef AdministrativeControl {
        description "Reflects the current control action when the entity is not in the desired state.
            The possible values of the current target administrative state.
            lifecycle:Experimental";
        type enumeration {
            enum UNLOCK;
            enum LOCK_PASSIVE;
            enum LOCK_ACTIVE;
            enum LOCK_IMMEDIATE;
        }
    }
    typedef ExtendedAdminState {
        description "Possible extentions to AdministrativeState
            lifecycle:Experimental";
        type enumeration {
            enum LOCKED;
            enum UNLOCKED;
            enum SHUTTING_DOWN_ACTIVE;
            enum SHUTTING_DOWN_PASSIVE;
        }
    }
    typedef LifecycleState {
        description "The possible values of the lifecycleState.
            lifecycle:Experimental";
        type enumeration {
            enum PLANNED;
            enum POTENTIAL;
            enum INSTALLED;
            enum PENDING_REMOVAL;
        }
    }
}
