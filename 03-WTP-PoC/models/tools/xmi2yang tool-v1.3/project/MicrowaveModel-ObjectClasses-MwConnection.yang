module MicrowaveModel-ObjectClasses-MwConnection {
    namespace "uri:onf:MicrowaveModel-ObjectClasses-MwConnection";
    prefix MicrowaveModel-ObjectClasses-MwConnection;

    import CoreModel-CoreFoundationModule-SuperClassesAndCommonPackages {
        prefix CoreModel-CoreFoundationModule-SuperClassesAndCommonPackages;
    }
    import CoreModel-CoreNetworkModule-ObjectClasses {
        prefix CoreModel-CoreNetworkModule-ObjectClasses;
    }
    import MicrowaveModel-TypeDefinitions {
        prefix MicrowaveModel-TypeDefinitions;
    }
    import CoreModel-CoreFoundationModule-TypeDefinitions {
        prefix CoreModel-CoreFoundationModule-TypeDefinitions;
    }
    import G_874_1_model-Object_Classes {
        prefix G_874_1_model-Object_Classes;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-09 {
        description 
            "Initial revision."; 
        reference 
            "ONF TR xyz: A YANG Data Model for Microwave Transport Networks."; 
    }

    list MW_AirInterface_Pac {
        description "LTP(MWPS-TTP)";
        key 'layerProtocol';
        config true;
        uses CoreModel-CoreFoundationModule-SuperClassesAndCommonPackages:LocalClass;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container airInterfaceCapability {
            uses AirInterfaceCapability;
        }
        container airInterfaceConfiguration {
            config true;
            uses AirInterfaceConfiguration;
        }
        container airInterfaceStatus {
            uses AirInterfaceStatus;
        }
        leaf-list airInterfaceCurrentProblemList {
            ordered-by system;
            type leafref {
                path '/MicrowaveModel-ObjectClasses-MwConnection:AirInterfaceCurrentProblem/MicrowaveModel-ObjectClasses-MwConnection:uuid';
            }
        }
        leaf airInterfaceCurrentPerformance {
            type leafref {
                path '/MicrowaveModel-ObjectClasses-MwConnection:AirInterfaceCurrentPerformance/MicrowaveModel-ObjectClasses-MwConnection:uuid';
            }
        }
        leaf-list airInterfaceHistoricalPerformanceList {
            ordered-by system;
            type leafref {
                path '/MicrowaveModel-ObjectClasses-MwConnection:AirInterfaceHistoricalPerformance/MicrowaveModel-ObjectClasses-MwConnection:uuid';
            }
        }
    }
    grouping AirInterfaceCapability {
        description "Describes the 'analog' capabilities of modem and transmitter of the microwave device. Value ranges of attributes are not independently (e.g. min. and max. transmit power depends on modulation). Legal combinations of values are expressed in transmissionModeTypes.
            Basic principles for defining the Default values of Capability attributes: 1)NO Default values for attributes that MUST be delivered from the device. 2)Default values for every attribute that might be delivered. 3)The Default value shall be inside the value range of the data type of the attribute. 4)The Default value shall be outside the range of reasonable values of the attribute.";
        uses CoreModel-CoreFoundationModule-SuperClassesAndCommonPackages:LocalClass;
        leaf typeOfEquipment {
            type string;
            config false;
            description "This parameter indicates the equipment type. Instead of uploading the complete set of capabilities, capabilities of the same equipment type could be reused.";
        }
        leaf txFrequencyMin {
            type int64;
            config false;
            description "Value of the minimum transmit frequency tunable at the air interface. This value is only relevant, if the channel plan, which is referenced in channelPlanID is stored in the controller.";
            units "kHz";
        }
        leaf txFrequencyMax {
            type int64;
            config false;
            description "Value of the maximum transmit frequency tunable at the air interface. This value is only relevant, if the channel plan, which is referenced in channelPlanID is stored in the controller.";
            units "kHz";
        }
        leaf rxFrequencyMin {
            type int64;
            config false;
            description "Value of the minimum receive frequency tunable at the air interface. This value is only relevant, if the channel plan, which is referenced in channelPlanID is stored in the controller.";
            units "kHz";
        }
        leaf rxFrequencyMax {
            type int64;
            config false;
            description "Value of the maximum receive frequency tunable at the air interface. This value is only relevant, if the channel plan, which is referenced in channelPlanID is stored in the controller.";
            units "kHz";
        }
        leaf adaptiveModulationIsAvail {
            type boolean;
            config false;
            description "In case the Air Interface Port is capable of adaptive modulation, this field shall contain an '1'.";
        }
        leaf mimoIsAvail {
            type boolean;
            config false;
            description "In case the device is capable of MIMO, this field shall contain an '1'.";
        }
        leaf mimoChannels {
            type int32 {
                range "1..4";
            }
            config false;
            description "Maximum number (n) of Air Interfaces that can be combined to a n x n MIMO configuration.";
            default 1;
        }
        leaf alicIsAvail {
            type boolean;
            config false;
            description "In case the microwave radio is capable of Adjacent Link Interference Cancelation (canceling of interference cause by transmitters located at the same site), this field shall contain an '1'.";
        }
        leaf atpcIsAvail {
            type boolean;
            config false;
            description "In case the microwave radio is capable of ATPC, this field shall contain an '1'.";
        }
        leaf atpcRange {
            type int32;
            config false;
            description "Extent of the ATPC range.";
            units "dB";
        }
        leaf loopBackIsAvail {
            type boolean;
            config false;
            description "In case the radio is capable of looping back header information of the air interface, this field shall contain an '1'.";
        }
        leaf maintenanceTimerRange {
            type string;
            config false;
            description "The device shall describe the range of the configurable time of existence of any maintenance configuration (e.g. the loop back of microwave header information). A list of values shall be separated by commas. A value range shall be expressed by two values separated by a minus.";
            units "s";
        }
        leaf supportedAlarms {
            type string;
            config false;
            description "Available alarms to be listed. Mandatory:'aiConfigurationIsFaulty','signalIsLost','rslIsExceeded','temperatureIsExceeded','modemIsFaulty','radioIsFaulty' and 'modulationIsDownShifted'. Further alarms might be added by the device. Names are to be separated by commas.";
        }
        list supportedChannelPlanList {
            description "List of channel spacing that are supported by the device.";
            key 'channelPlanTypeId';
            ordered-by system;
            uses MicrowaveModel-TypeDefinitions:channelPlanType;
            min-elements 1;
        }
    }
    grouping AirInterfaceConfiguration {
        description "Configuration of the device.
            Basic principles for defining the Default values of Configuration attributes: 1)NO Default values for attributes that MUST be configured by the controller/operator while starting the device. 2)Default values for every attribute that might be configured also at a later stage. 3)The Default value shall be inside the value range of the data type of the attribute. 4)The Default value shall be outside the range of reasonable values of the attribute. 5)Unless there is a value, which the attribute always has right after starting the device.           Configuration messages provided by the device shall contain the current configuration.";
        uses CoreModel-CoreFoundationModule-SuperClassesAndCommonPackages:LocalClass;
        leaf airInterfaceName {
            type string;
            description "Operator specific microwave link ID (often used for coding area, type of element and sequential number).";
            default "Air interface ID to be defined";
        }
        leaf radioSignalId {
            type string;
            description "The radioSignalId is transmitted on the air interface so the remote site of the link synchronizes on the correct transmitter. The local radio MUST NOT synchronize on a radio signal with a different radioSignalId. The link ID is neither an ID necessary to span the model nor an ID referencing external data. It is just some sort of name of the link transmitted so the correct remote site can be identified in an interference situation.
                The value zero might be used to make the microwave to disable the link ID check.";
        }
        leaf txFrequency {
            type int64;
            description "Center frequency of the transmit channel. The values to be configured have to exactly match the values listed in the international agreement referenced in channelPlanID. In case of automated selection of the transmit frequency this field shall describe the lowest center frequency selectable.";
            units "kHz";
        }
        leaf rxFrequency {
            type int64;
            description "Center frequency of the receive channel.";
            units "kHz";
        }
        leaf txChannelBandwidth {
            type int64;
            description "Bandwidth of the transmit channel. The value shall be expressed explicitly (means in kHz) not as a reference to an international agreement. The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;";
            units "kHz";
        }
        leaf rxChannelBandwidth {
            type int64;
            description "Bandwidth of the receive channel. The value shall be expressed explicitly (means in kHz) not as a reference to an international agreement. The values shall be chosen from the following _list: 3.500, 7.000, 14.000, 27.500, 28.000, 29.000, 29.650, 30.000, 40.000, 50.000, 55.000, 56.000, 59.300, 60.000, 80.000, 100.000, 112.000, 120.000, 150.000, 200.000, 250.000, 500.000, 750.000, 1.000.000, 1.250.000, 1.500.000, 1.750.000, 2.000.000;";
            units "kHz";
        }
        leaf polarization {
            type MicrowaveModel-TypeDefinitions:polarizationType;
            description "Allows to document the polarization of the air interface.";
        }
        leaf powerIsOn {
            type boolean;
            description "Power ON. Activation of the entire radio in a split mount configuration shall be expressed as an '1'.";
        }
        leaf transmitterIsOn {
            type boolean;
            description "Transmit Power. Activation of the transmitter inside the radio shall be expressed as an '1'.";
        }
        leaf txPower {
            type int32;
            description "Transmit power to be configured on the microwave link. Signed Byte is required. The actually operated transmit power might be lower depending on adaptive modulation and ATPC.";
            units "dBm";
        }
        leaf adaptiveModulationIsOn {
            type boolean;
            description "Adaptive Modulation. Activation of adaptive modulation shall be expressed as an '1'.";
        }
        leaf modulationMin {
            type int32;
            description "Minimum modulation to be configured (in case adaptive modulation is not used, this value represents also the fixed modulation). The modulation scheme shall be described by the number of symbols (e.g. BPSK->'2' or 256QAM->'256'). Allowed values are defined in AirInterface::Script::modulationScheme (all instances of the device).";
            units "symbols";
        }
        leaf modulationMax {
            type int32;
            description "Maximum modulation to be configured. The value of this field is only relevant, if Adaptive Modulation has been activated. The modulation scheme shall be described by the number of symbols (e.g. BPSK->'2' or 256QAM->'256'). Allowed values are defined in AirInterface::Script::modulationScheme (all instances of the device).";
            units "symbols";
            default 1;
        }
        leaf xpicIsOn {
            type boolean;
            description "Activation of Cross Polarization Interference Cancellation shall be expressed as a 'true'. In case XPIC is not available for the current combination of channel bandwidth and modulation or the hardware in general, this parameter shall always be set to 'false'.";
        }
        leaf mimoIsOn {
            type boolean;
            description "Activation of Multiple Input Multiple Output shall be expressed as an '1'.";
        }
        leaf alicIsOn {
            type boolean;
            description "Activation of Adjacent Link Interference Cancelation (ALIC) shall be expressed as an '1'.";
        }
        leaf atpcIsOn {
            type boolean;
            description "ATPC. Activation of Automated Transmit Power Control shall be expressed as an '1'.";
        }
        leaf atpcThreshUpper {
            type int32;
            description "If the receive level is higher than the upper threshold value, the transmitter is notified to decrease transmit power.";
            units "dBm";
            default 99;
        }
        leaf atpcThreshLower {
            type int32;
            description "If the receive level is lower than the lower threshold value, the transmitter is notified to increase transmit power.";
            units "dBm";
            default 99;
        }
        leaf autoFreqSelectIsOn {
            type boolean;
            description "Activation of automatically selecting the transmit frequency in unlicensed bands shall be expressed as an '1'.";
        }
        leaf autoFreqSelectRange {
            type int32;
            description "Number of transmit channels (starting at the center frequency defined in txFrequency and with channel bandwidth according to txChannelBandwidth) that define the range within the transmit frequency can automatically been chosen. ";
            default -1;
        }
        leaf modulationIsOn {
            type boolean;
            description "Maintenance Feature
                De-activation of the modulation of the carrier signal for fault management shall be expressed as an '0'.";
        }
        leaf loopBackIsOn {
            type boolean;
            description "Maintenance Feature
                If this attribute is set to '1', the received IF signal is transmitted back to the remote end.";
        }
        leaf maintenanceTimer {
            type int64;
            description "Time of existence of any maintenance configuration (e.g. the loop back of microwave header information). Allowed values are defined in AirInterface::AirInterfaceCapability::maintenanceTimerRange.";
            units "s";
            default -1;
        }
        list problemSeverityList {
            description "Severity of the problem to be configured.";
            key 'problemId';
            config true;
            ordered-by system;
            uses MicrowaveModel-TypeDefinitions:airInterfaceProblemType;
            min-elements 7;
        }
    }
    grouping AirInterfaceStatus {
        description "Measurements of current values on the air interface and operational status of the device.
            Basic principles for defining the Defaults values of Status attributes: 1)Every attribute shall have a Default value. 2)The Default value shall be inside the value range of the data type of the attribute. 3)The Default value shall be outside the range of reasonable values of the attribute. 4)Unless there is a value, which the attribute always has right after starting the device. 5)Status messages provided by the device shall either contain actual status information or if not possible these default values.";
        uses CoreModel-CoreFoundationModule-SuperClassesAndCommonPackages:LocalClass;
        leaf txFrequencyCur {
            type int64;
            config false;
            description "Center frequency of the currently operated transmit channel.";
            units "kHz";
            default 1;
        }
        leaf rxFrequencyCur {
            type int64;
            config false;
            description "Center frequency of the currently operated receive channel.";
            units "kHz";
            default 1;
        }
        leaf txLevelCur {
            type int32;
            config false;
            description "Current transmit level. Signed Byte is required.";
            units "dBm";
            default -99;
        }
        leaf rxLevelCur {
            type int32;
            config false;
            description "Current receive level. Signed Byte is required.";
            units "dBm";
            default 99;
        }
        leaf modulationCur {
            type int32;
            config false;
            description "Currently operated modulation on transmit path. The modulation scheme shall be described by the number of symbols (e.g. BPSK->'2' or 256QAM->'256'). Allowed values are defined in AirInterface::Script::modulationScheme (all instances of the device).";
            units "symbols";
            default 1;
        }
        leaf informationRateCur {
            type int32;
            config false;
            description "Information rate of the currently operated coding scheme.";
            units "%";
            default 101;
        }
        leaf snrCur {
            type int32;
            config false;
            description "Currently measured signal to noise ratio.";
            units "dB";
            default -99;
        }
        leaf xpdCur {
            type int32;
            config false;
            description "Currently measured cross polarization discrimination.";
            units "dB";
            default -99;
        }
        leaf rfTempCur {
            type int32;
            config false;
            description "Current temperature of the radio module inside the outdoor unit.";
            units "C";
            default -99;
        }
        leaf lastStatusChange {
            type CoreModel-CoreFoundationModule-TypeDefinitions:DateAndTime;
            config false;
            description "Time the Air Interface entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
        leaf radioPowerIsUp {
            type boolean;
            config false;
            description "If the radio unit has power and is switched on, this shall be expressed as an '1'.";
        }
        leaf linkIsUp {
            type boolean;
            config false;
            description "If connection is established to the remote site with the same linkID, this shall be expressed as an '1'.";
        }
        leaf xpicIsUp {
            type boolean;
            config false;
            description "If XPIC is currently actually working (not just configured), this shall be expressed as an '1'.";
        }
        leaf mimoIsUp {
            type boolean;
            config false;
            description "If MIMO is currently actually working (not just configured), this shall be expressed as an '1'.";
        }
        leaf alicIsUp {
            type boolean;
            config false;
            description "If Adjacent Link Interference Cancelation (ALIC) is currently actually working (not just configured), this shall be expressed as an '1'.";
        }
        leaf atpcIsUp {
            type boolean;
            config false;
            description "If ATPC is currently actually working (not just configured), this shall be expressed as an '1'.";
        }
        leaf autoFreqSelectIsUp {
            type boolean;
            config false;
            description "If automated frequency selection is currently actually working (not just configured), this shall be expressed as an '1'.";
        }
        leaf loopBackIsUp {
            type boolean;
            config false;
            description "If loop back of the air interface header is currently active (not just configured), this shall be expressed as an '1'.";
        }
    }
    list AirInterfaceCurrentProblem {
        key 'uuid';
        config true;
        ordered-by system;
        uses AirInterfaceCurrentProblem;
    }
    grouping AirInterfaceCurrentProblem {
        uses MwCurrentProblem;
        uses CoreModel-CoreFoundationModule-SuperClassesAndCommonPackages:LocalClass;
        container problem {
            uses MicrowaveModel-TypeDefinitions:airInterfaceProblemType;
        }
    }
    list AirInterfaceCurrentPerformance {
        key 'uuid';
        config true;
        ordered-by system;
        uses AirInterfaceCurrentPerformance;
    }
    grouping AirInterfaceCurrentPerformance {
        uses G_874_1_model-Object_Classes:OTN_CurrentData;
        uses CoreModel-CoreFoundationModule-SuperClassesAndCommonPackages:LocalClass;
    }
    list AirInterfaceHistoricalPerformance {
        key 'uuid';
        config true;
        ordered-by system;
        uses AirInterfaceHistoricalPerformance;
    }
    grouping AirInterfaceHistoricalPerformance {
        description "Consolidated performance informantion of the air interface.
            Basic principles for defining the Defaults values of Performance attributes: 1)Every attribute shall have a Default value. 2)The Default value shall be inside the value range of the data type of the attribute. 3)The Default value shall be outside the range of reasonable values of the attribute.";
        uses G_874_1_model-Object_Classes:OTN_HistoryData;
        uses CoreModel-CoreFoundationModule-SuperClassesAndCommonPackages:LocalClass;
        leaf es {
            type int64;
            config false;
            description "Number of errored seconds.";
            units "s";
            default -1;
        }
        leaf ses {
            type int64;
            config false;
            description "Number of severely errored seconds.";
            units "s";
            default -1;
        }
        leaf cses {
            type int64;
            config false;
            description "Number of consecutive severely errored seconds.";
            units "s";
            default -1;
        }
        leaf unavailability {
            type int64;
            config false;
            description "Total time of unavailability in seconds.";
            units "s";
            default -1;
        }
        leaf txLevelMin {
            type int32;
            config false;
            description "Minimum transmit power. Signed integers are required.";
            units "dBm";
            default -99;
        }
        leaf txLevelMax {
            type int32;
            config false;
            description "Maximum transmit power. Signed integers are required.";
            units "dBm";
            default -99;
        }
        leaf txLevelAvg {
            type int32;
            config false;
            description "Average transmit power. Signed integers are required.";
            units "dBm";
            default -99;
        }
        leaf rxLevelMin {
            type int32;
            config false;
            description "Minimum receive level. Signed integers are required.";
            units "dBm";
            default 99;
        }
        leaf rxLevelMax {
            type int32;
            config false;
            description "Maximum receive level. Signed integers are required.";
            units "dBm";
            default 99;
        }
        leaf rxLevelAvg {
            type int32;
            config false;
            description "Average receive level. Signed integers are required.";
            units "dBm";
            default 99;
        }
        leaf time2Symbols {
            type int64;
            config false;
            units "s";
            default -1;
        }
        leaf time4SymbolsS {
            type int64;
            config false;
            description "Sum of all seconds the transmitter operated in e.g. 4QAM strong.";
            units "s";
            default -1;
        }
        leaf time4Symbols {
            type int64;
            config false;
            units "s";
            default -1;
        }
        leaf time8Symbols {
            type int64;
            config false;
            units "s";
            default -1;
        }
        leaf time16SymbolsS {
            type int64;
            config false;
            units "s";
            default -1;
        }
        leaf time16Symbols {
            type int64;
            config false;
            units "s";
            default -1;
        }
        leaf time32Symbols {
            type int64;
            config false;
            units "s";
            default -1;
        }
        leaf time64Symbols {
            type int64;
            config false;
            units "s";
            default -1;
        }
        leaf time128Symbols {
            type int64;
            config false;
            units "s";
            default -1;
        }
        leaf time256Symbols {
            type int64;
            config false;
            units "s";
            default -1;
        }
        leaf time512Symbols {
            type int64;
            config false;
            units "s";
            default -1;
        }
        leaf time512SymbolsL {
            type int64;
            config false;
            units "s";
            default -1;
        }
        leaf time1024Symbols {
            type int64;
            config false;
            units "s";
            default -1;
        }
        leaf time1024SymbolsL {
            type int64;
            config false;
            units "s";
            default -1;
        }
        leaf time2048Symbols {
            type int64;
            config false;
            units "s";
            default -1;
        }
        leaf time2048SymbolsL {
            type int64;
            config false;
            units "s";
            default -1;
        }
        leaf time4096Symbols {
            type int64;
            config false;
            units "s";
            default -1;
        }
        leaf time4096SymbolsL {
            type int64;
            config false;
            units "s";
            default -1;
        }
        leaf time8192Symbols {
            type int64;
            config false;
            units "s";
            default -1;
        }
        leaf time8192SymbolsL {
            type int64;
            config false;
            units "s";
            default -1;
        }
        leaf snrMin {
            type int32;
            config false;
            description "Minimum signal to noise ratio.";
            units "dB";
            default -99;
        }
        leaf snrMax {
            type int32;
            config false;
            description "Maximum signal to noise ratio.";
            units "dB";
            default -99;
        }
        leaf snrAvg {
            type int32;
            config false;
            description "Average signal to noise ratio.";
            units "dB";
            default -99;
        }
        leaf xpdMin {
            type int32;
            config false;
            description "Minimum cross polarization discrimination.";
            units "dB";
            default -99;
        }
        leaf xpdMax {
            type int32;
            config false;
            description "Maximum cross polarization discrimination.";
            units "dB";
            default -99;
        }
        leaf xpdAvg {
            type int32;
            config false;
            description "Average cross polarization discrimination.";
            units "dB";
            default -99;
        }
        leaf rfTempMin {
            type int32;
            config false;
            description "Lowest temperature of the radio module inside the outdoor unit.";
            units "C";
            default -99;
        }
        leaf rfTempMax {
            type int32;
            config false;
            description "Highest temperature of the radio module inside the outdoor unit.";
            units "C";
            default -99;
        }
        leaf rfTempAvg {
            type int32;
            config false;
            description "Average temperature of the radio module inside the outdoor unit.";
            units "C";
            default -99;
        }
        leaf defectBlocksSum {
            type int32;
            config false;
            description "Total number of blocks that were defect after receiving and could not be corrected by the FEC.";
            default -1;
        }
        leaf timePeriod {
            type int64;
            config false;
            description "Total length of the measurement period.";
            units "s";
            default -1;
        }
    }
    list CoChannelGroup {
        key 'uuid';
        config true;
        uses CoreModel-CoreFoundationModule-SuperClassesAndCommonPackages:GlobalClass;
        leaf-list airInterfaceList {
            description "List of air interfaces, which are part of the co-channel (XPIC, MIMO, AFR) group.";
            ordered-by system;
            type leafref {
                path '/CoreModel-CoreNetworkModule-ObjectClasses:NetworkElement/CoreModel-CoreNetworkModule-ObjectClasses:_ltpRefList/CoreModel-CoreNetworkModule-ObjectClasses:uuid';
            }
        }
        leaf coSortOfChannelGroup {
            type string;
            description "Type of group of air interfaces with the same transmit and receive frequency. The values shall be chosen from the following _list:'XPIC', 'MIMO', 'AFR';";
        }
    }
    list MW_AirInterfaceDiversity_Pac {
        description "LTP(MWS-CTP-xD)";
        key 'layerProtocol';
        config true;
        ordered-by system;
        uses CoreModel-CoreFoundationModule-SuperClassesAndCommonPackages:LocalClass;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container airInterfaceDiversityCapability {
            uses AirInterfaceDiversityCapability;
        }
        container airInterfaceDiversityConfiguration {
            config true;
            uses AirInterfaceDiversityConfiguration;
        }
        container airInterfaceDiversityStatus {
            uses AirInterfaceDiversityStatus;
        }
        leaf-list airInterfaceDiversityCurrentProblemList {
            ordered-by system;
            type leafref {
                path '/MicrowaveModel-ObjectClasses-MwConnection:AirInterfaceDiversityCurrentProblem/MicrowaveModel-ObjectClasses-MwConnection:uuid';
            }
        }
        leaf airInterfaceDiversityCurrentPerformance {
            type leafref {
                path '/MicrowaveModel-ObjectClasses-MwConnection:AirInterfaceDiversityCurrentPerformance/MicrowaveModel-ObjectClasses-MwConnection:uuid';
            }
        }
        leaf-list airInterfaceDiversityHistoricalPerformanceList {
            ordered-by system;
            type leafref {
                path '/MicrowaveModel-ObjectClasses-MwConnection:AirInterfaceDiversityHistoricalPerformance/MicrowaveModel-ObjectClasses-MwConnection:uuid';
            }
        }
    }
    grouping AirInterfaceDiversityCapability {
        description "Describes the capabilities in implementing different types of air interface diversity.
            Basic principles for defining the Default values of Capability attributes: 1)NO Default values for attributes that MUST be delivered from the device. 2)Default values for every attribute that might be delivered. 3)The Default value shall be inside the value range of the data type of the attribute. 4)The Default value shall be outside the range of reasonable values of the attribute.";
        uses CoreModel-CoreFoundationModule-SuperClassesAndCommonPackages:LocalClass;
        list availableKindsOfDiversity {
            description "Available types of diversity to be listed.";
            key 'diversityTypeId';
            ordered-by system;
            uses MicrowaveModel-TypeDefinitions:diversityType;
        }
        leaf supportedAlarms {
            type string;
            config false;
            description "Available alarms to be listed.
                Mandatory:'airInterfaceDiversityConfigurationIsFaulty','airInterfaceDiversityConfigurationIsPartlyDown' and 'airInterfaceDiversityConfigurationIsDown'.
                Names are to be separated by commas.
                Further alarms might be added by the device.";
        }
    }
    grouping AirInterfaceDiversityConfiguration {
        description "Basic principles for defining the Default values of Configuration attributes: 1)NO Default values for attributes that MUST be configured by the controller/operator while starting the device. 2)Default values for every attribute that might be configured also at a later stage. 3)The Default value shall be inside the value range of the data type of the attribute. 4)The Default value shall be outside the range of reasonable values of the attribute. 5)Unless there is a value, which the attribute always has right after starting the device. 6)Configuration messages provided by the device shall contain the current configuration.";
        uses CoreModel-CoreFoundationModule-SuperClassesAndCommonPackages:LocalClass;
        container airInterfaceDiversity {
            description "Type of air interface diversity configured at the link.";
            config true;
            uses MicrowaveModel-TypeDefinitions:diversityType;
        }
        leaf-list airInterfaceLtpList {
            description "_multiplicity:2-ThisAirInterfaceDiversity::AirInterfaceDiversityConfiguration::airInterfaceDiversity::diversityType::numberOfAirInterfacesMax";
            ordered-by system;
            type leafref {
                path '/CoreModel-CoreNetworkModule-ObjectClasses:NetworkElement/CoreModel-CoreNetworkModule-ObjectClasses:_ltpRefList/CoreModel-CoreNetworkModule-ObjectClasses:uuid';
            }
            min-elements 2;
        }
        list problemSeverityList {
            description "Severity of the problem to be configured.";
            key 'problemId';
            config true;
            ordered-by system;
            uses MicrowaveModel-TypeDefinitions:airInterfaceDiversityProblemType;
            min-elements 3;
        }
    }
    grouping AirInterfaceDiversityStatus {
        description "Basic principles for defining the Defaults values of Status attributes: 1)Every attribute shall have a Default value. 2)The Default value shall be inside the value range of the data type of the attribute. 3)The Default value shall be outside the range of reasonable values of the attribute. 4)Unless there is a value, which the attribute always has right after starting the device. 5)Status messages provided by the device shall either contain actual status information or if not possible these default values.";
        uses CoreModel-CoreFoundationModule-SuperClassesAndCommonPackages:LocalClass;
        leaf lastStatusChange {
            type CoreModel-CoreFoundationModule-TypeDefinitions:DateAndTime;
            config false;
            description "Time the Diversity Group entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
        leaf airInterfaceDiversityStatus {
            type MicrowaveModel-TypeDefinitions:airInterfaceDiversityStatusType;
            config false;
            description "Status of the air interface bundle. ";
            default "groupDown";
        }
    }
    list AirInterfaceDiversityCurrentProblem {
        key 'uuid';
        config true;
        ordered-by system;
        uses AirInterfaceDiversityCurrentProblem;
    }
    grouping AirInterfaceDiversityCurrentProblem {
        uses MwCurrentProblem;
        uses CoreModel-CoreFoundationModule-SuperClassesAndCommonPackages:LocalClass;
        container problem {
            uses MicrowaveModel-TypeDefinitions:airInterfaceDiversityProblemType;
        }
    }
    list AirInterfaceDiversityCurrentPerformance {
        key 'uuid';
        config true;
        ordered-by system;
        uses AirInterfaceDiversityCurrentPerformance;
    }
    grouping AirInterfaceDiversityCurrentPerformance {
        uses G_874_1_model-Object_Classes:OTN_CurrentData;
        uses CoreModel-CoreFoundationModule-SuperClassesAndCommonPackages:LocalClass;
    }
    list AirInterfaceDiversityHistoricalPerformance {
        key 'uuid';
        config true;
        ordered-by system;
        uses AirInterfaceDiversityHistoricalPerformance;
    }
    grouping AirInterfaceDiversityHistoricalPerformance {
        uses G_874_1_model-Object_Classes:OTN_HistoryData;
        uses CoreModel-CoreFoundationModule-SuperClassesAndCommonPackages:LocalClass;
    }
    list MW_Structure_Pac {
        description "LTP(MWS-TTP)";
        key 'layerProtocol';
        config true;
        uses CoreModel-CoreFoundationModule-SuperClassesAndCommonPackages:LocalClass;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container structureCapability {
            uses StructureCapability;
        }
        container structureConfiguration {
            config true;
            uses StructureConfiguration;
        }
        container structureStatus {
            uses StructureStatus;
        }
        leaf-list structureCurrentProblemList {
            ordered-by system;
            type leafref {
                path '/MicrowaveModel-ObjectClasses-MwConnection:StructureCurrentProblem/MicrowaveModel-ObjectClasses-MwConnection:uuid';
            }
        }
        leaf structureCurrentPerformance {
            type leafref {
                path '/MicrowaveModel-ObjectClasses-MwConnection:StructureCurrentPerformance/MicrowaveModel-ObjectClasses-MwConnection:uuid';
            }
        }
        leaf-list structureHistoricalPerformanceList {
            ordered-by system;
            type leafref {
                path '/MicrowaveModel-ObjectClasses-MwConnection:StructureHistoricalPerformance/MicrowaveModel-ObjectClasses-MwConnection:uuid';
            }
        }
    }
    grouping StructureCapability {
        description "Describes the logical structuring of the physical capacity provided by the microwave device.
            Basic principles for defining the Default values of Capability attributes: 1)NO Default values for attributes that MUST be delivered from the device. 2)Default values for every attribute that might be delivered. 3)The Default value shall be inside the value range of the data type of the attribute. 4)The Default value shall be outside the range of reasonable values of the attribute.";
        uses CoreModel-CoreFoundationModule-SuperClassesAndCommonPackages:LocalClass;
        leaf structureID {
            type string;
            config false;
            description "Identifies the Structure for bundling and container.";
        }
        leaf timeSlotCapacity {
            type int32;
            config false;
            description "Transport capacity of each time slot.";
            units "kbit/s";
            default 2048;
        }
        leaf totalNumberOfTimeSlots {
            type int32;
            config false;
            description "Maximum number of time slots available with the current configuration of the air interface (means e.g. that AirInterface::AirInterfaceStatus::modulationCur is equal to AirInterface::AirInterfaceConfiguration::modulationMax).";
        }
        leaf tdmTimeSlotsIsSupported {
            type boolean;
            config false;
            description "In case the microwave radio is capable of transporting TDM, this field shall contain an '1'.";
        }
        leaf supportedAlarms {
            type string;
            config false;
            description "Available alarms to be listed.
                Mandatory:'structureConfigurationIsFaulty'.
                Names are to be separated by commas.
                Further alarms might be added by the device.";
        }
    }
    grouping StructureConfiguration {
        description "Basic principles for defining the Default values of Configuration attributes: 1)NO Default values for attributes that MUST be configured by the controller/operator while starting the device. 2)Default values for every attribute that might be configured also at a later stage. 3)The Default value shall be inside the value range of the data type of the attribute. 4)The Default value shall be outside the range of reasonable values of the attribute. 5)Unless there is a value, which the attribute always has right after starting the device. 6)Configuration messages provided by the device shall contain the current configuration.";
        uses CoreModel-CoreFoundationModule-SuperClassesAndCommonPackages:LocalClass;
        leaf tdmReservedNumberOfTimeSlots {
            type int32;
            description "Allows to configure the number of time slots reserved for TDM traffic.";
            default -1;
        }
        list problemSeverityList {
            description "Severity of the type of problem to be configured.";
            key 'problemId';
            config true;
            ordered-by system;
            uses MicrowaveModel-TypeDefinitions:structureProblemType;
            min-elements 1;
        }
    }
    grouping StructureStatus {
        description "Basic principles for defining the Defaults values of Status attributes: 1)Every attribute shall have a Default value. 2)The Default value shall be inside the value range of the data type of the attribute. 3)The Default value shall be outside the range of reasonable values of the attribute. 4)Unless there is a value, which the attribute always has right after starting the device. 5)Status messages provided by the device shall either contain actual status information or if not possible these default values.";
        uses CoreModel-CoreFoundationModule-SuperClassesAndCommonPackages:LocalClass;
        list timeSlotStatusList {
            description "Condition of each time slot.
                _multiplicity:Structure::StructureCapability::totalNumberOfTimeSlots";
            key 'timeSlotStatusTypeId';
            ordered-by system;
            uses MicrowaveModel-TypeDefinitions:timeSlotStatusType;
        }
        leaf lastStatusChange {
            type CoreModel-CoreFoundationModule-TypeDefinitions:DateAndTime;
            config false;
            description "Time and date of the last update of the status information.
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
        }
    }
    list StructureCurrentProblem {
        key 'uuid';
        config true;
        ordered-by system;
        uses StructureCurrentProblem;
    }
    grouping StructureCurrentProblem {
        uses MwCurrentProblem;
        uses CoreModel-CoreFoundationModule-SuperClassesAndCommonPackages:LocalClass;
        container problem {
            uses MicrowaveModel-TypeDefinitions:structureProblemType;
        }
    }
    list StructureCurrentPerformance {
        key 'uuid';
        config true;
        ordered-by system;
        uses StructureCurrentPerformance;
    }
    grouping StructureCurrentPerformance {
        uses G_874_1_model-Object_Classes:OTN_CurrentData;
        uses CoreModel-CoreFoundationModule-SuperClassesAndCommonPackages:LocalClass;
    }
    list StructureHistoricalPerformance {
        key 'uuid';
        config true;
        ordered-by system;
        uses StructureHistoricalPerformance;
    }
    grouping StructureHistoricalPerformance {
        description "Basic principles for defining the Defaults values of Performance attributes:
            - Every attribute shall have a Default value.
            - The Default value shall be inside the value range of the data type of the attribute.
            - The Default value shall be outside the range of reasonable values of the attribute.";
        uses G_874_1_model-Object_Classes:OTN_HistoryData;
        uses CoreModel-CoreFoundationModule-SuperClassesAndCommonPackages:LocalClass;
        leaf timePeriod {
            type int64;
            config false;
            description "Total length of the measurement period in seconds.
                Required data volume = 17bit";
            units "s";
            default -1;
        }
    }
    list MW_Container_Pac {
        description "LTP(Client)";
        key 'layerProtocol';
        config true;
        ordered-by system;
        uses CoreModel-CoreFoundationModule-SuperClassesAndCommonPackages:LocalClass;
        leaf layerProtocol {
            type leafref {
                path '/CoreModel-CoreNetworkModule-ObjectClasses:NetworkElement/CoreModel-CoreNetworkModule-ObjectClasses:_ltpRefList/CoreModel-CoreNetworkModule-ObjectClasses:_lpList/CoreModel-CoreNetworkModule-ObjectClasses:uuid';
            }
            description "CoreModel-CoreNetworkModule-ObjectClasses:NetworkElement/_ltpRefList/_lpList/uuid";
        }
        container containerCapability {
            uses ContainerCapability;
        }
        container containerConfiguration {
            config true;
            uses ContainerConfiguration;
        }
        container containerStatus {
            uses ContainerStatus;
        }
        leaf-list containerCurrentProblemList {
            ordered-by system;
            type leafref {
                path '/MicrowaveModel-ObjectClasses-MwConnection:ContainerCurrentProblem/MicrowaveModel-ObjectClasses-MwConnection:uuid';
            }
        }
        leaf containerCurrentPerformance {
            type leafref {
                path '/MicrowaveModel-ObjectClasses-MwConnection:ContainerCurrentPerformance/MicrowaveModel-ObjectClasses-MwConnection:uuid';
            }
        }
        leaf-list containerHistoricalPerformanceList {
            ordered-by system;
            type leafref {
                path '/MicrowaveModel-ObjectClasses-MwConnection:ContainerHistoricalPerformance/MicrowaveModel-ObjectClasses-MwConnection:uuid';
            }
        }
    }
    grouping ContainerCapability {
        description "Basic principles for defining the Default values of Capability attributes: 1)NO Default values for attributes that MUST be delivered from the device. 2)Default values for every attribute that might be delivered. 3)The Default value shall be inside the value range of the data type of the attribute. 4)The Default value shall be outside the range of reasonable values of the attribute.";
        uses CoreModel-CoreFoundationModule-SuperClassesAndCommonPackages:LocalClass;
        leaf containerID {
            type string;
            config false;
            description "ContainterID in Netconf must be the same as EthernetPortID in OpenFlow so a connection can be made between the two items, which are existing separately in the controller.";
        }
        list availableKindsOfContainerList {
            description "Available container types to be listed.";
            key 'containerTypeId';
            ordered-by system;
            uses MicrowaveModel-TypeDefinitions:containerType;
            min-elements 1;
        }
        leaf priorityClassesIsAvail {
            type boolean;
            config false;
            description "Shall be marked '1', if the device is capable of assigning different priorities to containers and adapting the sequence, in which time slots are being dropped in case of decreasing capacity of the air interface.";
        }
        leaf encryptionIsAvail {
            type boolean;
            config false;
            description "Shall be marked '1', if payload encryption is available.";
        }
        leaf packetCompressionIsAvail {
            type boolean;
            config false;
            description "In case packet compression can be activated, but not configured to a certain type, packetCompressionAvail shall be set to '1', but none of the type specific booleans.";
        }
        leaf layer2CompressionIsAvail {
            type boolean;
            config false;
            description "Packet compression on layer 2 available at the device.";
        }
        leaf vlanCompressionIsAvail {
            type boolean;
            config false;
            description "Packet compression on VLAN layer available at the device.";
        }
        leaf qInQCompressionIsAvail {
            type boolean;
            config false;
            description "Packet compression on layer of a second VLAN available at the device.";
        }
        leaf mplsCompressionIsAvail {
            type boolean;
            config false;
            description "Packet compression on mpls layer available at the device.";
        }
        leaf l2vpnCompressionIsAvail {
            type boolean;
            config false;
            description "Packet compression on level of layer 2 VPN available at the device.";
        }
        leaf ipv4CompressionIsAvail {
            type boolean;
            config false;
            description "Packet compression on layer 3 for IPv4 available at the device.";
        }
        leaf ipv6CompressionIsAvail {
            type boolean;
            config false;
            description "Packet compression on layer 3 for IPv6 available at the device.";
        }
        leaf l3vpnCompressionIsAvail {
            type boolean;
            config false;
            description "Packet compression on level of layer 3 VPN available at the device.";
        }
        leaf layer4CompressionIsAvail {
            type boolean;
            config false;
            description "Packet compression on layer 4 (TCP and UDP header) available at the device.";
        }
        leaf supportedAlarms {
            type string;
            config false;
            description "Available alarms to be listed.
                Mandatory:'containerConfigurationIsFaulty','framingIsFaulty' and 'containerIsDown'.
                Names are to be separated by commas.
                Further alarms might be added by the device.";
        }
    }
    grouping ContainerConfiguration {
        description "Basic principles for defining the Default values of Configuration attributes: 1)NO Default values for attributes that MUST be configured by the controller/operator while starting the device. 2)Default values for every attribute that might be configured also at a later stage. 3)The Default value shall be inside the value range of the data type of the attribute. 4)The Default value shall be outside the range of reasonable values of the attribute. 5)Unless there is a value, which the attribute always has right after starting the device. 6)Configuration messages provided by the device shall contain the current configuration.";
        uses CoreModel-CoreFoundationModule-SuperClassesAndCommonPackages:LocalClass;
        container container {
            description "Defines the data type of the container offered to client layers.";
            config true;
            uses MicrowaveModel-TypeDefinitions:containerType;
        }
        leaf priorityClass {
            type int32;
            description "0 = lowest and 7 = highest Priority. Any value apart the Default is only effective if the device is capable of adapting the sequence, in which time slots are being dropped in case of decreasing capacity of the air interface.";
        }
        list timeSlotIDList {
            description "Lists the time slots used for transporting this container. In case ThisContainer::ContainerConfiguration::container::containerType::bundlingIsAvail==0, structureId must be equal for all aiTimeSlots in the list.
                _multiplicity:ThisContainer::ContainerConfiguration::container::containerType::numberOfTimeSlotsRequired";
            key 'structureId timeSlotId';
            config true;
            ordered-by system;
            uses MicrowaveModel-TypeDefinitions:timeSlotIdType;
            min-elements 1;
        }
        leaf encryptionIsOn {
            type boolean;
            description "Activates encryption of the payload.";
        }
        leaf packetCompressionIsOn {
            type boolean;
            config false;
            description "In case packet compression is activated, but no type is activated, it is assumed that the device choses an optimum.";
        }
        leaf layer2CompressionIsOn {
            type boolean;
            config false;
            description "Packet compression on layer 2 configured at the device.";
        }
        leaf vlanCompressionIsOn {
            type boolean;
            config false;
            description "Packet compression on VLAN layer configured at the device.";
        }
        leaf qInQCompressionIsOn {
            type boolean;
            config false;
            description "Packet compression on layer of a second VLAN configured at the device.";
        }
        leaf mplsCompressionIsOn {
            type boolean;
            config false;
            description "Packet compression on MPLS layer configured at the device.";
        }
        leaf l2vpnCompressionIsOn {
            type boolean;
            config false;
            description "Packet compression on level of layer 2 VPN configured at the device.";
        }
        leaf ipv4CompressionIsOn {
            type boolean;
            config false;
            description "Packet compression on layer 3 for IPv4 configured at the device.";
        }
        leaf ipv6CompressionIsOn {
            type boolean;
            config false;
            description "Packet compression on layer 3 for IPv6 configured at the device.";
        }
        leaf l3vpnCompressionIsOn {
            type boolean;
            config false;
            description "Packet compression on level of layer 3 VPN configured at the device.";
        }
        leaf layer4CompressionIsOn {
            type boolean;
            config false;
            description "Packet compression on layer 4 (TCP and UDP header) configured at the device.";
        }
        list problemSeverityList {
            description "Severity of the problem to be configured.";
            key 'problemId';
            config true;
            ordered-by system;
            uses MicrowaveModel-TypeDefinitions:containerProblemType;
            min-elements 3;
        }
    }
    grouping ContainerStatus {
        description "Basic principles for defining the Defaults values of Status attributes: 1)Every attribute shall have a Default value. 2)The Default value shall be inside the value range of the data type of the attribute. 3)The Default value shall be outside the range of reasonable values of the attribute. 4)Unless there is a value, which the attribute always has right after starting the device. 5)Status messages provided by the device shall either contain actual status information or if not possible these default values.";
        uses CoreModel-CoreFoundationModule-SuperClassesAndCommonPackages:LocalClass;
        leaf lastStatusChange {
            type CoreModel-CoreFoundationModule-TypeDefinitions:DateAndTime;
            config false;
            description "Time the Container entered its current operational status. 
                _format:yyyyMMddhhmmss.s[Z|{+|-}HHMm]; yyyy='0000'..'9999' year; MM='01'..'12' month; dd='01'..'31' day; hh='00'..'23' hour; mm='00'..'59' minute; ss='00'..'59' second; s='.0'..'.9'tenth of second (set to '.0' if EMS or NE cannot support this granularity); Z='Z' indicates UTC (rather than local time); {+|-}='+' or '-' delta from UTC; HH='00'..'23' time zone difference in hours; Mm='00'..'59' time zone difference in minutes.";
            default "20101120140000.0Z+1";
        }
        leaf dropOrderRank {
            type int32;
            config false;
            description "dropOrderRank as inherited from the associated Structure::StructureStatus::timeSlotStatusType::dropOrderRank. If several time slots are associated, the lowest value shall be taken.";
            default -1;
        }
    }
    list ContainerCurrentProblem {
        key 'uuid';
        config true;
        ordered-by system;
        uses ContainerCurrentProblem;
    }
    grouping ContainerCurrentProblem {
        uses MwCurrentProblem;
        uses CoreModel-CoreFoundationModule-SuperClassesAndCommonPackages:LocalClass;
        container problem {
            uses MicrowaveModel-TypeDefinitions:containerProblemType;
        }
    }
    list ContainerCurrentPerformance {
        key 'uuid';
        config true;
        ordered-by system;
        uses ContainerCurrentPerformance;
    }
    grouping ContainerCurrentPerformance {
        uses G_874_1_model-Object_Classes:OTN_CurrentData;
        uses CoreModel-CoreFoundationModule-SuperClassesAndCommonPackages:LocalClass;
    }
    list ContainerHistoricalPerformance {
        key 'uuid';
        config true;
        ordered-by system;
        uses ContainerHistoricalPerformance;
    }
    grouping ContainerHistoricalPerformance {
        description "Basic principles for defining the Defaults values of Performance attributes: 1)Every attribute shall have a Default value. 2)The Default value shall be inside the value range of the data type of the attribute. 3)The Default value shall be outside the range of reasonable values of the attribute.";
        uses G_874_1_model-Object_Classes:OTN_HistoryData;
        uses CoreModel-CoreFoundationModule-SuperClassesAndCommonPackages:LocalClass;
        leaf txEthernetBytesMaxS {
            type int64;
            config false;
            description "Counts the number of Bytes of Ethernet traffic (before header compression) transmitted within a second and keeps the highest value within the measurement period. Field to be left blank for all types of TDM containers.
                Required data volume = 31bit";
            units "Bytes/s";
            default 1;
        }
        leaf txEthernetBytesMaxM {
            type int64;
            config false;
            description "Counts the number of Bytes of Ethernet traffic (before header compression) transmitted within a minute and keeps the highest value with in the measurement period. Field to be left blank for all types of TDM containers.
                Required data volume = 37bit";
            units "Bytes/min";
            default 1;
        }
        leaf txEthernetBytesSum {
            type int64;
            config false;
            description "Total number of Bytes of Ethernet traffic (before header compression) transmitted (in direction out of the device) during the measurement period. Field to be left blank for all types of TDM containers.
                Required data volume = 47bit";
            units "Bytes";
            default 1;
        }
        leaf timePeriod {
            type int64;
            config false;
            description "Total length of the measurement period in seconds.
                Required data volume = 17bit";
            units "s";
            default -1;
        }
    }
    list MwCurrentProblem {
        key 'sequenceNumber';
        config true;
        ordered-by system;
        uses MwCurrentProblem;
    }
    grouping MwCurrentProblem {
        description "According to ITU-T G.874.1?";
        leaf sequenceNumber {
            type int64;
            description "Unique sequence number of the current problem object.";
        }
        leaf timeStamp {
            type CoreModel-CoreFoundationModule-TypeDefinitions:DateAndTime;
        }
        leaf severity {
            type MicrowaveModel-TypeDefinitions:severityType;
            config false;
        }
    }
}
