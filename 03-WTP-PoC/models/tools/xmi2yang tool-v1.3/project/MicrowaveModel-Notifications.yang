module MicrowaveModel-Notifications {
    namespace "uri:onf:MicrowaveModel-Notifications";
    prefix MicrowaveModel-Notifications;

    import CoreModel-CoreFoundationModule-TypeDefinitions {
        prefix CoreModel-CoreFoundationModule-TypeDefinitions;
    }
    import CoreModel-CoreFoundationModule-SuperClassesAndCommonPackages {
        prefix CoreModel-CoreFoundationModule-SuperClassesAndCommonPackages;
    }
    import MicrowaveModel-TypeDefinitions {
        prefix MicrowaveModel-TypeDefinitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-07-09 {
        description 
            "Initial revision."; 
        reference 
            "ONF TR xyz: A YANG Data Model for Microwave Transport Networks."; 
    }

    notification ObjectCreationNotification {
        description "To be sent when a new MW_AirInterface_Pac, MW_AirInterfaceDiversity_Pac, MW_Structure_Pac or MW_Container_Pac has to be instancieted in the controller.";
        leaf counter {
            type int64;
            description "Counts object creation notifications.";
        }
        leaf timeStamp {
            type CoreModel-CoreFoundationModule-TypeDefinitions:DateAndTime;
        }
        leaf objectID {
            type CoreModel-CoreFoundationModule-SuperClassesAndCommonPackages:UniversalId;
            description "ID of the affected MW_AirInterface_Pac, MW_AirInterfaceDiversity_Pac, MW_Structure_Pac or MW_Container_Pac";
        }
        leaf objectType {
            type string;
            description "Type of Object to be chosen from the following list of values: 'MW_AirInterface_Pac', 'MW_AirInterfaceDiversity_Pac', 'MW_Structure_Pac', 'MW_Container_Pac'";
        }
    }
    notification ObjectDeletionNotification {
        description "To be sent when a MW_AirInterface_Pac, MW_AirInterfaceDiversity_Pac, MW_Structure_Pac or MW_Container_Pac instance has to be deleted in the controller.";
        leaf counter {
            type int64;
            description "Counts object deletion notifications.";
        }
        leaf timeStamp {
            type CoreModel-CoreFoundationModule-TypeDefinitions:DateAndTime;
        }
        leaf objectID {
            type CoreModel-CoreFoundationModule-SuperClassesAndCommonPackages:UniversalId;
            description "ID of the affected MW_AirInterface_Pac, MW_AirInterfaceDiversity_Pac, MW_Structure_Pac or MW_Container_Pac";
        }
    }
    notification AttributeValueChangedNotification {
        description "To be sent when an attribute has changed and one or more controllers have to update their data.";
        leaf counter {
            type int64;
            description "Counts attribute value changed notifications.";
        }
        leaf timeStamp {
            type CoreModel-CoreFoundationModule-TypeDefinitions:DateAndTime;
        }
        leaf objectID {
            type CoreModel-CoreFoundationModule-SuperClassesAndCommonPackages:UniversalId;
            description "ID of the affected MW_AirInterface_Pac, MW_AirInterfaceDiversity_Pac, MW_Structure_Pac or MW_Container_Pac";
        }
        leaf attributeName {
            type string;
            description "Name of the attribute that has been changed.";
        }
        leaf newValue {
            type string;
            description "Attribute value converted to a sring (xml, json, ...)";
        }
    }
    notification ProblemNotification {
        description "To be sent when a problem occurs at a MW_AirInterface_Pac, MW_AirInterfaceDiversity_Pac, MW_Structure_Pac or a MW_Container_Pac.";
        leaf counter {
            type int64;
            description "Counts problem notifications";
        }
        leaf timeStamp {
            type CoreModel-CoreFoundationModule-TypeDefinitions:DateAndTime;
        }
        leaf objectID {
            type CoreModel-CoreFoundationModule-SuperClassesAndCommonPackages:UniversalId;
            description "ID of the affected MW_AirInterface_Pac, MW_AirInterfaceDiversity_Pac, MW_Structure_Pac or MW_Container_Pac";
        }
        leaf problem {
            type string;
            description "Name of the problem according to AirInterface::AirInterfaceCapability::supportedAlarms or AirInterfaceDiversity::AirInterfaceDiversityCapability::supportedAlarms or Structure::StructureCapability::supportedAlarms or Container::ContainerCapability::supportedAlarms";
        }
        leaf severity {
            type MicrowaveModel-TypeDefinitions:severityType;
            description "Severity of the problem according to AirInterface::AirInterfaceConfiguration::problemSeverityList, AirInterfaceDiversity::AirInterfaceDiversityConfiguration::problemSeverityList, Structure::StructureConfiguration::problemSeverityList and Container::ContainerConfiguration::problemSeverityList";
        }
    }
}
