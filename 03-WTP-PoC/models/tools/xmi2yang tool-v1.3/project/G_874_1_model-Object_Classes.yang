module G_874_1_model-Object_Classes {
    namespace "uri:onf:G_874_1_model-Object_Classes";
    prefix G_874_1_model-Object_Classes;

    import G_874_1_model-Imported_Information_Object_Classes-Q_822 {
        prefix G_874_1_model-Imported_Information_Object_Classes-Q_822;
    }
    import G_874_1_model-Type_Definitions {
        prefix G_874_1_model-Type_Definitions;
    }

    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        '<p>Version 2.02; outcome of the 10/2013 Nuremberg meeting.<br>Version 2.03; updates for Geneva 03-2014<br>Version 2.04; updates for Shanghai 09-2014<br>Version 2.05; input to Geneva 11-2014<br>Version 2.06; output from Geneva 11-2014<br>Version 2.07; using OpenProfile 3-2015<br>Version 2.08; output from Geneva 06-2015</p>';

    revision 2016-07-09 {
        description 
            "Initial revision."; 
        reference 
            "ONF TR xyz: A YANG Data Model for Microwave Transport Networks."; 
    }

    grouping OTN_CurrentData {
        description "This object class is an abstract class from which the OTN layer-specific CurrentData object classes are inherited. This object class is a subclass of the Q.822 CurrentData object class, which in turn is a subclass of X.739 Scanner object class. It inherits the following attributes: scannerId, operationalState, granularityPeriod, administrativeState, suspectIntervalFlag, elapsedTime, observedObjectClass, and observedObjectInstance.";
        uses G_874_1_model-Imported_Information_Object_Classes-Q_822:Q_822_CurrentData;
        leaf timestamp {
            type G_874_1_model-Type_Definitions:DateAndTime;
            description "The timestamp associated with when the current data was collected.";
        }
    }
    grouping OTN_HistoryData {
        description "This object class is an abstract class from which the OTN layer-specific HistoryData object classes are inherited. ";
        uses G_874_1_model-Imported_Information_Object_Classes-Q_822:Q_822_HistoryData;
        leaf suspectIntervalFlag {
            type boolean;
            description "This attribute indicates that the data collected during the interval is suspect.";
            default "false";
        }
    }
}
