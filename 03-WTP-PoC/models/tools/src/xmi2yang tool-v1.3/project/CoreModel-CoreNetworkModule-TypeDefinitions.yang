module CoreModel-CoreNetworkModule-TypeDefinitions {
    namespace "uri:onf:CoreModel-CoreNetworkModule-TypeDefinitions";
    prefix CoreModel-CoreNetworkModule-TypeDefinitions;


    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        'This module contains a collection of YANG definitions for 
         managing microwave transport networks.';

    revision 2016-08-09 {
        description 
            "Initial revision."; 
        reference 
            "ONF TR xyz: A YANG Data Model for Microwave Transport Networks."; 
    }

    typedef OperType {
        description "The operation type associated with the protection mechanism (either non-revertive or revertive).";
        type enumeration {
            enum REVERTIVE;
            enum NON-REVERTIVE;
        }
    }
    typedef LayerProtocolName {
        description "Provides a controlled list of layer protocol names and indicates the naming authority.Note that it is expected that attributes will be added to this structure to convey the naming authority name, the name of the layer protocol using a human readable string and any particular standard reference.Layer protocol names include:-    Layer 1 (L1): OTU, ODU-    Layer 2 (L2): Carrier Grade Ethernet (ETY, ETH), MPLS-TP (MT)
            lifecycle:Preliminary";
        type string;
    }
    typedef PortRole {
        description "The role of a port in the context of the function of the forwarding entity that it bounds
            lifecycle:Preliminary";
        type string;
    }
    typedef PortDirection {
        description "The orientation of flow at the Port of a Forwarding entity";
        type enumeration {
            enum BIDIRECTIONAL;
            enum INPUT;
            enum OUTPUT;
            enum UNIDENTIFIED_OR_UNKNOWN;
        }
    }
    typedef ForwardingDirection {
        description "The directionality of a Forwarding entity.";
        type enumeration {
            enum BIDIRECTIONAL;
            enum UNIDIRECTIONAL;
            enum UNDEFINED_OR_UNKNOWN;
        }
    }
    typedef TerminationDirection {
        description "The directionality of a termination entity";
        type enumeration {
            enum BIDIRECTIONAL;
            enum SINK;
            enum SOURCE;
            enum UNDEFINED_OR_UNKNOWN;
        }
    }
    typedef ExtendedTerminationDirection {
        description "Extended to include contra-direction considerations. Only applies to LP and elements of LP not to LTP??
            lifecycle:Experimental";
        type enumeration {
            enum BIDIRECTIONAL;
            enum SINK;
            enum SOURCE;
            enum UNDEFINED_OR_UNKNOWN;
            enum CONTRA_DIRECTION_SINK;
            enum CONTRA_DIRECTION_SOURCE;
        }
    }
    typedef ProtectionType {
        description "Identifies the type of rotection of an FcSwitch.
            lifecycle:Experimental";
        type string;
    }
    typedef TerminationState {
        description "Provides support for the range of behaviours and specific states that an LP can take with respect to termination of the signal.Indicates to what degree the LayerTermination is terminated.
            lifecycle:Experimental";
        type enumeration {
            enum LP_CAN_NEVER_TERMINATE;
            enum LT_NOT_TERMINATED;
            enum TERMINATED_SERVER_TO_CLIENT_FLOW;
            enum TERMINATED_CLIENT_TO_SERVER_FLOW;
            enum TERMINATED_BIDIRECTIONAL;
            enum LT_PERMENANTLY_TERMINATED;
            enum TERMINATION_STATE_UNKNOWN;
        }
    }
}
