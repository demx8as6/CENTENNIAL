module G_874_1_model-Type_Definitions {
    namespace "uri:onf:G_874_1_model-Type_Definitions";
    prefix G_874_1_model-Type_Definitions;


    organization 
        'ONF (Open Networking Foundation) Open Transport Working Group - Wireless Transport Project';

    contact 
        'WG Web:   <https://www.opennetworking.org/technical-communities/areas/specification/1931-optical-transport>
         WG List:  <mailto:wireless-transport@login.opennetworking.org >
         WG Chair: Lyndon Ong
                   <mailto:lyong@ciena.com>
         WG Chair: Giorgio Cazzaniga
                   <mailto:giorgio.cazzaniga@sm-optics.com>';

    description 
        '<p>Version 2.02; outcome of the 10/2013 Nuremberg meeting.<br>Version 2.03; updates for Geneva 03-2014<br>Version 2.04; updates for Shanghai 09-2014<br>Version 2.05; input to Geneva 11-2014<br>Version 2.06; output from Geneva 11-2014<br>Version 2.07; using OpenProfile 3-2015<br>Version 2.08; output from Geneva 06-2015</p>';

    revision 2016-08-09 {
        description 
            "Initial revision."; 
        reference 
            "ONF TR xyz: A YANG Data Model for Microwave Transport Networks."; 
    }

    typedef Directionality {
        description "The enumeration with the options for directionality of the termination point.";
        type enumeration {
            enum SINK;
            enum SOURCE;
            enum BIDIRECTIONAL;
        }
    }
    typedef GccAccess {
        description "This enumeration indicates the GCC access represented by the entity.";
        type enumeration {
            enum GCC1;
            enum GCC2;
            enum GCC1_AND_GCC2;
        }
    }
    typedef OperationalState {
        description "The list of valid operational states for the connection.";
        type enumeration {
            enum ENABLED;
            enum DISABLED;
        }
    }
    typedef OperType {
        description "The operation type associated with the protection mechanism (either non-revertive or revertive).";
        type enumeration {
            enum REVERTIVE;
            enum NON-REVERTIVE;
        }
    }
    typedef ExtCmdOperation {
        description "This enumeration contains the options for the actions that instruct the protection system for performing specific protection switching operations.";
        type enumeration {
            enum EXERCISE;
            enum MANUAL_SWITCH;
            enum FORCED_SWITCH;
            enum LOCKOUT;
            enum RELEASE_OF_MANUAL_SWITCH;
            enum RELEASE_OF_FORCED_SWITCH;
            enum RELEASE_OF_LOCKOUT;
        }
    }
    typedef AdministrativeState {
        description "For more information on Administrative State, See ITU-T Recs. X.731 and M.3100.";
        type enumeration {
            enum UNLOCKED;
            enum LOCKED;
            enum SHUTTING_DOWN;
        }
    }
    typedef OCTk_NimKBitRate {
        description "Provides an enumeration with the meaning of each 'k' value.";
        type enumeration {
            enum 2.5_G;
            enum 10_G;
            enum 40_G;
            enum 100_G;
        }
    }
    typedef TimDetMo {
        description "List of modes for trace identifier mismatch detection.";
        type enumeration {
            enum DAPI;
            enum SAPI;
            enum BOTH;
        }
    }
    typedef OCTk_NimProblemList {
        description "The valid list of problems for the entity.";
        type enumeration {
            enum LOS_P;
            enum OCI;
            enum SSF_P;
            enum SSF_O;
            enum SSF;
            enum TIM;
            enum DEG;
            enum BDI;
        }
    }
    typedef TcmMonitoring {
        description "Monitoring types for the tandem connection monitoring function.";
        type enumeration {
            enum INTRUSIVE;
            enum NON-INTRUSIVE;
        }
    }
    typedef TcmMode {
        description "List of value modes for the sink side of the tandem connection monitoring function.";
        type enumeration {
            enum OPERATIONAL;
            enum TRANSPARENT;
            enum MONITOR;
        }
    }
    typedef OPSMnk_TtpKBitRate {
        description "Provides an enumeration with the meaning of each 'k' value.";
        type enumeration {
            enum 40_G;
            enum 100_G;
        }
    }
    typedef OPSMnk_TtpProblemList {
        description "The valid list of problems for the entity.";
        type enumeration {
            enum LOS;
            enum LOL;
        }
    }
    typedef OPSn_TtpProblemList {
        description "The valid list of problems for the entity.";
        type enumeration {
            enum LOS;
        }
    }
    typedef OTM_n_KBitRates {
        description "Provides an enumeration with the meaning of each 'k' value.";
        type enumeration {
            enum 2.5_G;
            enum 10_G;
            enum 40_G;
            enum 2.5_10_G;
            enum 10_40_G;
            enum 2.5_10_40_G;
        }
    }
    typedef DomainInterface {
        description "This enumeration provides the options for the interface associated with OTMn.";
        type enumeration {
            enum INTRA_DOMAIN;
            enum INTER_DOMAIN;
        }
    }
    typedef OTM_n_OpticalReach {
        description "The valid options for reach of the optical cable.";
        type enumeration {
            enum INTRA_OFFICE;
            enum SHORTHAUL;
            enum LONGHAUL;
        }
    }
    typedef AprStatus {
        description "The enumeration of the options for the Automatic Power Reduction Status.";
        type enumeration {
            enum ON;
            enum OFF;
        }
    }
    typedef OTSn_TtpProblemList {
        description "The valid list of problems for the entity.";
        type enumeration {
            enum BDI_P;
            enum BDI_O;
            enum BDI;
            enum TIM;
            enum LOS_P;
            enum LOS_O;
            enum LOS;
        }
    }
    typedef OTUk_CtpAdaptation {
        description "The adaptation options for OTUk_ConnectionTermationPoints.";
        type enumeration {
            enum REGULAR;
            enum NONE;
            enum VENDOR_SPECIFIC;
            enum FUNCTIONALLY_STANDARDIZED;
        }
    }
    typedef OTUk_CtpKBitRate {
        description "Provides an enumeration with the meaning of each 'k' value.";
        type enumeration {
            enum 2.5_G;
            enum 10_G;
            enum 40_G;
            enum 100_G;
        }
    }
    typedef OTUk_CtpProblemList {
        description "The valid list of problems for the entity.";
        type enumeration {
            enum LOF;
            enum AIS;
            enum LOM;
        }
    }
    typedef OTUk_TtpProblemList {
        description "The valid list of problems for the entity.";
        type enumeration {
            enum TIM;
            enum DEG;
            enum BDI;
            enum SSF;
        }
    }
    typedef MonitoredDirection {
        description "The enumeration with the options for directionality for nonintrusive monitoring.";
        type enumeration {
            enum SINK;
            enum SOURCE;
        }
    }
    typedef DegThrType {
        description "<p>The value of the threshold can be provisioned in terms of number of errored blocks or in terms of percentage of errored blocks. For percentage-based specification, in order to support provision of less than 1%, the specification consists of two fields. The first field indicates the granularity of percentage. For examples, in 1%, in 0.1%, or in 0.01%, etc. The second field indicates the multiple of the granularity. For number of errored block based, the value is a positive integer.</p>";
        type enumeration {
            enum PERCENTAGE;
            enum NUMBER_ERRORED_BLOCKS;
        }
    }
    typedef LinkType {
        type enumeration {
            enum DWDM;
            enum CWDM;
            enum NO_WDM;
        }
    }
    typedef ApplicationIdentifierType {
        type enumeration {
            enum STANDARD;
            enum PROPRIETARY;
        }
    }
    typedef PrintableString {
        type string;
    }
    typedef DateAndTime {
        description "This primitive type defines the date and time according to the following structure:'yyyyMMddhhmmss.s[Z|{+|-}HHMm]' where:yyyy    '0000'..'9999'    yearMM        '01'..'12'            monthdd        '01'..'31'            dayhh        '00'..'23'            hourmm        '00'..'59'            minutess        '00'..'59'            seconds        '.0'..'.9'            tenth of second (set to '.0' if EMS or NE cannot support this granularity)Z        'Z'                    indicates UTC (rather than local time){+|-}    '+' or '-'            delta from UTCHH        '00'..'23'            time zone difference in hoursMm        '00'..'59'            time zone difference in minutes.";
        type string;
    }
    typedef ApsChannel {
        type enumeration {
            enum PATH;
            enum TCM1;
            enum TCM2;
            enum TCM3;
            enum TCM4;
            enum TCM5;
            enum TCM6;
            enum SECTION;
        }
    }
    typedef BitString {
        description "This primitive type defines a bit oriented string.The size of the BitString will be defined in the valueRange property of the attribute; according to ASN.1 (X.680).The semantic of each bit position will be defined in the Documentation field of the attribute.";
        type string;
    }
    typedef DelayMeasurementRole {
        type enumeration {
            enum CONTROLLER;
            enum RESPONDER;
        }
    }
    typedef ResizeOperationType {
        type enumeration {
            enum INCREASE_BW;
            enum DECREASE_BW;
        }
    }
    typedef GranularityPeriodType {
        description "The enumeration with the options for granularity period of the performance data.";
        type enumeration {
            enum UNKNOWN;
            enum PERIOD_15MIN;
            enum PERIOD_24HOURS;
        }
    }
}
